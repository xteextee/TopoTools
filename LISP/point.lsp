(defun c:vername ( / e i j m n p s )
(if (setq s (ssget '((0 . "LWPOLYLINE"))))
(repeat (setq i (sslength s))
(setq e (ssname s (setq i (1- i)))
n (cdr (assoc 210 (entget e)))
m (vlax-curve-getendparam e)
j -1
)
(while (<= (setq j (1+ j)) m)
(setq p (trans (vlax-curve-getpointatparam e j) 0 e))
(entmakex
(list
(cons 0 "TEXT")
(cons 7 (getvar 'TEXTSTYLE))
(cons 40 (getvar 'TEXTSIZE))
(cons 10 p)
(cons 11 p)
(cons 72 1)
(cons 73 2)
(cons 1 (itoa (1+ j)))
(cons 210 n)
)
)
)
)
)
(princ)
)
